EXERCICIO-RFID-MIB DEFINITIONS ::= BEGIN

--
-- MIB Objects para o exercicio RFID da aula de Gestao de Redes
--

IMPORTS
    MODULE-IDENTITY, OBJECT-TYPE, Integer32, IpAddress,
    NOTIFICATION-TYPE, experimental         FROM SNMPv2-SMI
    RowStatus, StorageType, DisplayString   FROM SNMPv2-TC
    InetAddressType, InetAddress            FROM INET-ADDRESS-MIB
;

exercicioRFID  MODULE-IDENTITY
    LAST-UPDATED "201810290000Z"
    ORGANIZATION "www.mieti.uminho.pt"
    CONTACT-INFO    
	 "postal:   Azurem 
          email:    mieti@eng.uminho.pt"
    DESCRIPTION
	"Example MIB objects for agent module example implementations"
    REVISION     "201810290000Z"
    DESCRIPTION
	"Corrected notification example definitions"
    REVISION     "201810220000Z"
    DESCRIPTION
	"First draft"
    ::= { experimental 2018 }

--
-- top level structure
--

zona OBJECT-TYPE
    SYNTAX      DisplayString
    MAX-ACCESS  read-write
    STATUS      current
    DESCRIPTION
	"Identifica a zona dentro da oficina... cada zona tem varias areas"
    ::= { exercicioRFID 1 }

leitorRFID OBJECT-TYPE
    SYNTAX      OCTET STRING
    MAX-ACCESS  read-write
    STATUS      current
    DESCRIPTION
	"Identifica o leitor RFID pertencente a uma zona da oficina... "
    ::= { exercicioRFID 2 }

agente OBJECT-TYPE
    SYNTAX      IpAddress
    MAX-ACCESS  read-write
    STATUS      current
    DESCRIPTION
	"Endereco IP do agente que controla o leitor RFID da zona "
    ::= { exercicioRFID 3 }

nAreas OBJECT-TYPE
    SYNTAX      Integer32
    MAX-ACCESS  read-write
    STATUS      current
    DESCRIPTION
	"Numero de areas dentro de uma zona..."
    ::= { exercicioRFID 4 }

--
--  Tabela de RFID 
--

tableRFID OBJECT-TYPE
    SYNTAX      SEQUENCE OF RFIDTableEntry
    MAX-ACCESS  not-accessible
    STATUS      current
    DESCRIPTION
	"Esta tabela mantem uma lista de veiculos por area...
     000000 se nao estiver la nenhum veiculo"
    ::= { exercicioRFID 5 }

tableEntryRFID OBJECT-TYPE
    SYNTAX      RFIDTableEntry
    MAX-ACCESS  not-accessible
    STATUS      current
    DESCRIPTION
	"Uma linha da tabela com: areaId, tag, areaDescr"
    INDEX   { areaID }
    ::= { tableRFID 1 }

RFIDTableEntry ::= SEQUENCE {
	areaID	Integer32,
	tag	OCTET STRING,
	areaDescr	DisplayString
}

areaID OBJECT-TYPE
    SYNTAX      Integer32 (1..32)
    MAX-ACCESS  not-accessible
    STATUS      current
    DESCRIPTION
	"Identificacao da Area"
    ::= { tableEntryRFID 1 }

tag OBJECT-TYPE
    SYNTAX      OCTET STRING (SIZE (6))
    MAX-ACCESS  read-create
    STATUS      current
    DESCRIPTION
	"Valor da etiqueta RFID lida pelo leitor RFID: 6bytes 
     Exemplos: 111111, 222222, 000000"
    ::= { tableEntryRFID 2 }

areaDescr OBJECT-TYPE
    SYNTAX      DisplayString
    MAX-ACCESS  read-create
    STATUS      current
    DESCRIPTION
	"Descricao da area"
    ::= { tableEntryRFID 3 }

END
